from FreeCAD import Rotation, Vector, Placement
from finger import Finger, Row
import FreeCAD as App
import FreeCADGui as Gui
import finger
import utils

# This is needed for development since FreeCAD uses cached version of library.
import importlib
importlib.reload(finger)
importlib.reload(utils)

# Document that stores the 'key' object and Spreadsheet for variables.
# key document contains the model for a single key support
source_doc = App.getDocument('Case')
doc = App.ActiveDocument

# Tried to use the same document as source of object and generated shapes. It's
# a huge headache, trust me.
if source_doc == doc:
    raise EnvironmentError('Run macro in different document than the Case '
                           'document that contains the key model.')

utils.clear_report()
utils.remove_all(doc)

DRAW_FINGERS = True               # Draw the cones to represent fingers.
DRAW_KEYS = True                 # Draw the actual keys.
FUSE_COLS = True and DRAW_KEYS    # Fuse the generated columns together.

# TODO: Generate the geometry needed to create the inter-key webbing instead of
# hard coding the edges from the key model.
PREV_KEY_EDGE = 'Edge75'   # Edges used to create the column webbing.
NEXT_KEY_EDGE = 'Edge79'  # These are required for fusing to work.

KEY_HEIGHT = -13.8    # Key was modeled in the negative z direction.
KEY_ROT = Rotation(finger.X_AXIS, 180)  # Apply correct orientation.


def add_key():
    """Copies the key from source document."""
    key = doc.copyObject(source_doc.getObjectsByLabel("key")[0])
    key.ViewObject.Visibility = True
    return key


def draw_hand(fingers):
    """ Goes through finger and draws the keys."""
    for f in fingers:
        shapes_to_merge = []
        prev_key = None
        surfs = []
        f.keys = []
        for i, _ in enumerate(f.rows):
            print('adding:', i)
            v, rot = f.get_pos(i, draw=DRAW_FINGERS)
            if DRAW_KEYS:
                key = add_key()
                f.keys.append(key)
                # Used to rotate and position at top of box.
                center_v = Vector(0, 0, KEY_HEIGHT)  # key.Shape.BoundBox.ZMin)
                key.Placement = Placement(v - center_v,
                                          rot.multiply(KEY_ROT),
                                          center_v)
                doc.recompute()

                if FUSE_COLS and prev_key:
                    surface = doc.addObject('Part::RuledSurface', 'surf')
                    surface.Curve1 = (prev_key, [PREV_KEY_EDGE])
                    surface.Curve2 = (key, [NEXT_KEY_EDGE])
                    surfs.append(surface)
                    doc.recompute()
                prev_key = key
                shapes_to_merge.append(key)

        if FUSE_COLS:
            for surf in surfs:
                webbing = doc.addObject('Part::Extrusion', 'surfjoin')
                webbing.Base = surf
                webbing.Solid = True
                webbing.DirMode = "Custom"
                webbing.Dir = Vector(-1, 0, 0)
                webbing.LengthFwd = source_doc.Spreadsheet.BaseWidth
                shapes_to_merge.append(webbing)
                doc.recompute()

        # Fuse and select for printing.
        if FUSE_COLS:
            print(shapes_to_merge)
            pr = doc.addObject("Part::MultiFuse", "stl_export")
            pr.Shapes = shapes_to_merge
            doc.recompute()
            Gui.Selection.addSelection(pr)


hand = []

# # Pinky
# hand.append(
#     Finger(
#         segments=Finger.generate_segments([40, 20, 20]),
#         rows=generate_finger_rows(Vector(), [[15, 45, 45]]),
#     )
# )

# # Ring finger
# hand.append(
#     Finger(
#         segments=Finger.generate_segments([50, 28, 22]),
#         rows=generate_finger_rows(Vector(25, 3, 0), [[10, 70, 10]]),
#     )
# )

# Middle finger
hand.append(
    Finger()
    .generate_segments([60, 30, 25])
    .add_rows(Vector(47, 8, 0),
              [([18, 5, 5], 40),
               ([15, 60, 10], 5)]))

# Index finger
hand.append(
    Finger()
    .generate_segments([55, 25, 20])
    .add_rows(Vector(70, 8, 0), [([18, 5, 5], 50),
                                 ([15, 27, 27], 25),
                                 ([16, 45, 45], 0)]))

# Index finger - secondary position
# i_rot=Rotation(finger.Z_AXIS, -20)
# # Side rotation
# i_rot_2=i_rot.multiply(Rotation(finger.X_AXIS, -5))
# i_rot_3=i_rot.multiply(Rotation(finger.X_AXIS, -20))
# i_rot_4=i_rot.multiply(Rotation(finger.X_AXIS, -40))
# fingers.append(
#     Finger(
#         color=(0.2, 0.2, 0.8),
#         segments=Finger.get_vecs([55, 25, 20]),
#         rows=[Row(resting=Row.get_mods([i_rot, 0, 5],
#                                        [Vector(40, 25, 0)])),
#               Row(resting=Row.get_mods([i_rot_2, 15, 15],
#                                        [Vector(40, 25, 0)])),
#               Row(resting=Row.get_mods([i_rot_3, 45, 25],
#                                        [Vector(40, 25, 0)])),
#               Row(resting=Row.get_mods([i_rot_4, 90, 45],
#                                        [Vector(40, 25, 0)]))]
#     ))

draw_hand(hand)

for fing in hand:
    print(fing.keys)
