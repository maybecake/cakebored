from PySide import QtGui
import Sketcher

doc = FreeCAD.ActiveDocument


def get_edge(sketch, vertex):
    """Returns edge and vertex number given sketch and vertex"""
    for num, edge in enumerate(sketch.Geometry, start=1):
        if hasattr(edge, 'StartPoint') and hasattr(edge, 'EndPoint'):
            print(num, '-', edge.StartPoint, edge.EndPoint)
            if edge.StartPoint == vertex:
                return (num, 1)
            if edge.EndPoint == vertex:
                return (num, 2)
        elif isinstance(edge, Part.Point):
            print(num, '-', edge.toShape())


def vert_align_points(objects, names):
    """Applies vertical constraints on all vertices in object."""
    ref_point = None
    for o, n in zip(objects, names):
        # index = re.match('.*?([0-9]+)$', n).group(1)
        # print(o, 'is', n, index)

        if o.ShapeType == 'Vertex':
            if not ref_point:
                ref_point = o
            else:
                pass
            # EdgeIndex, PointIndexOnEdge, edgeIndex, pointIndexOnEdge, floatstr(con.Value)
            #  sketch.addConstraint(Sketcher.Constraints(
            #     'DistanceY', 0, 1, 0, 2, 0))


mw = Gui.getMainWindow()
r = mw.findChild(QtGui.QTextEdit, "Report view")
r.clear()

for obj in doc.Objects:
    print('\n {}({}, {})'.format(obj.Label, obj.Name, obj.TypeId))
    if hasattr(obj, 'Type',):
        print('    type:', obj.Type, )
    if hasattr(obj, 'Shape'):
        print('    Shape type: {} {}'.format(
            obj.Shape.TypeId, obj.Shape.check()))
        print(obj.Shape.Wires, obj.Shape.Edges, obj.Shape.Vertexes)

print('\n {}'.format('='*30))
if len(Gui.Selection.getSelection()) > 0:
    selected = Gui.Selection.getSelection()[0]
print(selected)
if selected.TypeId == 'Sketcher::SketchObject':
    print('A sketch is selected.', selected.Label, '(', selected.Name)
    # w = selected.Shape
    # face = Part.Face(w)
    # print(face)
    # ex = face.extrude(FreeCAD.Vector(0, 0, 2))
    # print(ex)


# selArr = Gui.Selection.getSelectionEx()
# in_edit = Gui.ActiveDocument.getInEdit()

# if in_edit:
#     sketch = in_edit.Object
# # So, the whole selection system for FreeCAD sketches is a bit... sketchy.
# # Try to figure out what is actually selected:

# print('sketch:', sketch)
# get_edge(sketch, None)

# if len(selArr) == 1 and selArr[0].HasSubObjects:
#     objects = selArr[0].SubObjects
#     names = selArr[0].SubElementNames
#     print('names:', names)
#     if len(objects) != len(names):
#         print("selection elements do not match.")
#     vert_align_points(objects, names)
# else:
#     print("no selected object")
